//////////////////////////////////////////////////////////////////////////////
// MIT License
//
//Copyright (c) 2018 Alessio Occhiodoro
//
//Permission is hereby granted, free of charge, to any person obtaining a copy
//of this software and associated documentation files (the "Software"), to deal
//in the Software without restriction, including without limitation the rights
//to use, copy, modify, merge, publish, distribute, sublicense, and/or sell
//copies of the Software, and to permit persons to whom the Software is
//furnished to do so, subject to the following conditions:
//
//The above copyright notice and this permission notice shall be included in all
//copies or substantial portions of the Software.
//
//THE SOFTWARE IS PROVIDED "AS IS", WITHOUT WARRANTY OF ANY KIND, EXPRESS OR
//IMPLIED, INCLUDING BUT NOT LIMITED TO THE WARRANTIES OF MERCHANTABILITY,
//FITNESS FOR A PARTICULAR PURPOSE AND NONINFRINGEMENT. IN NO EVENT SHALL THE
//AUTHORS OR COPYRIGHT HOLDERS BE LIABLE FOR ANY CLAIM, DAMAGES OR OTHER
//LIABILITY, WHETHER IN AN ACTION OF CONTRACT, TORT OR OTHERWISE, ARISING FROM,
//OUT OF OR IN CONNECTION WITH THE SOFTWARE OR THE USE OR OTHER DEALINGS IN THE
//SOFTWARE.
//
// now it works with both schematics and boards
//////////////////////////////////////////////////////////////////////////////

#usage "<b>Create a markdown readme file for the project</b><p>\n"

if(board) board(B)
{
	string outputFileName = dlgFileSave("create .MD file", filesetext(B.name, ".md"), "*.md");

	if(outputFileName == "")
	{
		exit(0);
	}



		output(outputFileName)
		{
			printf("# %s Readme file\n", filename(B.name));
			printf("\n");
			printf("## Generated on: %s\n", t2string(time()));
			printf("\n");
			printf("### %s\n", EAGLE_SIGNATURE);
			printf("\n");
			printf("---");
			printf("\n");
			printf("## !!!!!!!URGENT!!!!!!!\n");
			printf("  * //\n");
			printf("\n");
			printf("\n");
			printf("### NOTES\n");
			printf("  * //\n");
			printf("\n");
			printf("\n");
			printf("### TODO EDITS\n");
			printf("  * //\n");
			printf("\n");
               printf("#### _TEST ROUTINE_\n");
			printf("  * //\n");
		}

}
else
{
  if(schematic) schematic(S)
  {
    string outputFileName = dlgFileSave("create .MD file", filesetext(S.name, ".md"), "*.md");

    if(outputFileName == "")
    {
	    exit(0);
    }



	  output(outputFileName)
  	{
	  	printf("# %s Readme file\n", filename(S.name));
	  	printf("\n");
	  	printf("## Generated on: %s\n", t2string(time()));
	  	printf("\n");
	  	printf("### %s\n", EAGLE_SIGNATURE);
	  	printf("\n");
	  	printf("---");
	  	printf("\n");
	  	printf("**!!!!!!!URGENT!!!!!!!**\n");
	  	printf("  * //\n");
	  	printf("\n");
	  	printf("\n");
	  	printf("**NOTES**\n");
	  	printf("  * //\n");
	  	printf("\n");
  	 	printf("\n");
  		printf("**TODO EDITS**\n");
 		  printf("  * //\n");
			printf("\n");
	  	printf("\n");
			printf("__TEST ROUTINE__\n");
			printf("  * //\n");
			printf("\n");
    }
	}

else
{
  dlgMessageBox("Daffuq ya doin bru?", "&OK");
}
}
